submodule e2-o-cu-cp {
  belongs-to e2node {
    prefix cp;
  }

  organization "Open Networking Foundation.";
  contact "Sean Condon";
  description "Configuration of E2Node Central Unit Control Plane";

  revision "2020-05-01" {
    description "Initial version";
    reference "ORAN-WG3.E2GAP-V01.00";
  }

  container e2-cp {
    presence "CU-CP is present";
    description "Configuration related to CU-CP";


  }
}
