submodule e2-o-du {
  belongs-to e2node {
    prefix du;
  }

  organization "Open Networking Foundation.";
  contact "Sean Condon";
  description "Configuration of E2Node Distributed Unit";

  revision "2020-05-01" {
    description "Initial version";
    reference "ORAN-WG3.E2GAP-V01.00";
  }

  container e2-du {
    presence "DU is present";
    description "Configuration related to DP";


  }
}
