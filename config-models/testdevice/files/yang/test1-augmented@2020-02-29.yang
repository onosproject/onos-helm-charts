module test1-augmented {
    namespace "http://opennetworking.org/devicesim/test1-augmented";
    prefix t1a;

    import test1 { prefix t1; }


    organization "Open Networking Foundation.";
    contact "Sean Condon";
    description "To generate JSON from this use command
      pyang -f jtoxx test1.yang | python3 -m json.tool > test1.json
      Copied from YangUIComponents project";

    revision "2020-02-29" {
      description "Augmented with new container with choice";
      reference "RFC 6087";
    }

    augment "/t1:cont1a" {
        container cont2d {
            leaf leaf2d3c {
                type string;
            }


           choice snack {
               description "straight from RFC-6020";
               case sports-arena {
                   leaf pretzel {
                       type empty;
                   }
                   leaf beer {
                       type empty;
                   }
               }
               case late-night {
                   leaf chocolate {
                       type enumeration {
                           enum dark;
                           enum milk;
                           enum first-available;
                       }
                   }
               }
           }
       }
    }
}
