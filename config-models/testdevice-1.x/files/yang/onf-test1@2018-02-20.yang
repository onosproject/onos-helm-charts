module onf-test1 {
  namespace "http://opennetworking.org/devicesim/test1";
  prefix t1;

  organization "Open Networking Foundation.";
  contact "Sean Condon";
  description "To generate JSON from this use command
    pyang -f jtoxx test1.yang | python3 -m json.tool > test1.json
    Copied from YangUIComponents project";

  revision "2018-02-20" {
    description "Used for testing different data node types";
    reference "RFC 6087";
  }

  container cont1a {
    presence "Top level is present";
    description "The top level container";

    container cont2a {
      description "The 2nd level container";

      leaf leaf2a {
        type uint8 {
          range 1..3|11..13;
        }
        units dB;
        default 2;
        description "Numeric leaf inside Container 2a";
        reference "RFC 6040";
      }
      leaf leaf2b {
        type decimal64 {
          fraction-digits 3;
          range 0.001..2.000;
        }
        units mV;
        mandatory true;
        description "Voltage leaf inside Container 2a";
      }
      leaf leaf2c {
        type string;
        config false;
        description "Read only leaf inside Container 2a";
      }
      leaf leaf2d {
        type decimal64 {
          fraction-digits 3;
          range 0.001..2.000;
        }
        description "Another decimal inside Container 2a";
      }
      leaf-list leaf2e {
        type int16 {
          range -100..200;
        }
        description "leaf list inside Container 2a";
      }
      leaf leaf2f {
        type binary {
          length 20;
        }
        description "binary leaf inside container 2a";
      }
      leaf leaf2g {
        type boolean;
        description "Boolean leaf inside Container 2a";
      }
    }

    leaf leaf1a {
      type string {
        length 5..10;
      }
      description "Leaf inside Container 1a";
    }

    list list2a {
      must "range-min < range-max" {
        error-message "range-min must be less than or equal to range-max";
        error-app-tag "range must";
        description "this is a must statement";
      }
      key name;
      max-elements 4;
      description "A simple list of configuration items";

      leaf name {
        type string {
          length 4..8;
        }
        description "The list is keyed by name";
      }

      leaf tx-power {
        type uint16 {
          range 1..20;
        }
        units mW;
        description "Transmit power";
      }

      leaf ref2d {
        type leafref {
            path /cont1a/cont2a/leaf2d;
        }
        description "A reference to leaf2d in the 2a container";
      }

      leaf range-min {
        type uint8;
        mandatory true;
        description "A simple range to test rules in YANG. Min must be <= max";
      }
      leaf range-max {
        type uint8;
        description "A max value for the range";
      }

    }
  }

  leaf leafAtTopLevel {
    type string {
      pattern "[A-Z]{3}-[0-9]*";
    }
    description "A leaf at the top level (not recommended but must be supported)";
  }

  container cont1b-state {
    config false;
    description "A second top level container - this one for state attributes. Edit symbol should not be visible";

    list list2b {
      key index;
      config false;
      description "A simple list of state items";

      leaf index {
        type uint8;
        description "The list index";
      }

      leaf leaf3c {
        type string {
          length 1..20;
        }
        config false;
        description "A string attribute in the list";
      }
    }

    leaf leaf2d {
      type uint16 {
        range 10000..20000;
      }
      units mm;
      config false;
      description "A state attribute";
    }
  }
}
