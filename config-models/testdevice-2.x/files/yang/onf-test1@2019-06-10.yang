module onf-test1 {
  namespace "http://opennetworking.org/devicesim/test1";
  prefix t1;

  import onf-test1-identities { prefix t1id; }

  organization "Open Networking Foundation.";
  contact "Sean Condon";
  description "To generate JSON from this use command
    pyang -f jtoxx test1.yang | python3 -m json.tool > test1.json
    Copied from YangUIComponents project";

  revision "2019-06-10" {
    description "Extended with new attributes on leaf2d, list2b";
    reference "RFC 6087";
  }

  revision "2018-02-20" {
    description "Used for testing different data node types";
    reference "RFC 6087";
  }

  container cont1a {
    presence "Top level is present";
    description "The top level container";

    container cont2a {
      must "leaf2g or leaf2a < 4" {
        error-message "If Leaf 2a is above 4 then leaf2g must be true for the validation to pass";
      }
      description "The 2nd level container";

      leaf leaf2a {
        type uint8 {
          range 1..3|11..13;
        }
        units dB;
        default 2;
        description "Numeric leaf inside Container 2a";
        reference "RFC 6040";
      }
      leaf leaf2b {
        type decimal64 {
          fraction-digits 3;
          range -0.001..2.000;
        }
        units mV;
        mandatory true;
        description "Voltage leaf inside Container 2a";
      }
      leaf leaf2c {
        type string;
        config false;
        description "Read only leaf inside Container 2a";
      }
      leaf leaf2d {
        type decimal64 {
          fraction-digits 3;
          range 0.001..2.000;
        }
        description "Another decimal inside Container 2a";
      }
      leaf-list leaf2e {
        type int16 {
          range -100..200;
        }
        description "leaf list inside Container 2a";
      }
      leaf leaf2f {
        type binary {
          length 20;
        }
        description "binary leaf inside Container 2a";
      }
      leaf leaf2g {
        type boolean;
        description "Boolean leaf inside Container 2a";
      }
    }

    leaf leaf1a {
      type string {
        length 5..10;
      }
      description "Leaf inside Container 1a";
    }

    list list2a {
      must "tx-power < rx-power" {
        error-message "tx-power is greater than or equal to rx-power";
        description "tx-power must be less than rx-power - the only value they can share is 20";
      }
      key name;
      max-elements 4;
      description "A simple list of configuration items";

      leaf name {
        type string {
          length 4..8;
        }
        description "The list is keyed by name";
      }

      leaf tx-power {
        type uint16 {
          range 1..20;
        }
        units mW;
        description "Transmit power";
      }
      leaf rx-power {
        type uint16 {
          range 20..30;
        }
        units mW;
        description "Receive power";
      }
    }


  }

  leaf leafAtTopLevel {
    type string {
      pattern "[A-Z]{3}-[0-9]*";
    }
    description "A leaf at the top level (not recommended but must be supported)";
  }

  container cont1b-state {
    config false;
    description "A second top level container - this one for state attributes. Edit symbol should not be visible";

    list list2b {
      key "index1 index2";
      config false;
      max-elements 3;
      description "A simple list of state items, with a double key";

      leaf index1 {
        type uint8;
        description "The list index";
      }

      leaf index2 {
          type uint8;
          description "The list index";
      }

      leaf leaf3c {
        type string {
          length 1..20;
        }
        config false;
        description "A string attribute in the list";
      }

      leaf leaf3d {
        type identityref {
            base t1id:MYBASE;
        }
        description "An identityref attribute in the list";
      }
    }

    leaf leaf2d {
      type uint16 {
        range 10000..20000;
      }
      units mm;
      config false;
      description "A state attribute";
    }

    container cont2c {
      description "This is a new container added in the 2019 version.  We don't have to say it's 'config false' - implied by parent";

      leaf leaf3a {
        type boolean;
        description "Another boolean variable";
      }
      leaf leaf3b {
        type string {
            length 5..10;
        }
        description "Another string variable";
      }
    }
  }
}
